module ietf-dhcpv6-relay {
  namespace "urn:ietf:params:xml:ns:yang:ietf-dhcpv6-relay";
  prefix "dhcpv6-client";

  import ietf-inet-types {
    prefix inet;
    revision-date "2013-07-15";
  }

  import ietf-dhcpv6-options {
    prefix dhcpv6-options;
    revision-date "2017-11-20";
  }

  organization "DHC WG";
  contact "yong@csnet1.cs.tsinghua.edu.cn
    wangh13@mails.tsinghua.edu.cn
    lh.sunlinh@gmail.com
    ian.farrer@telekom.de
    sladjana.zechlin@telekom.de";

  description "This model defines a YANG data model that can be
    used to configure and manage a DHCPv6 relay.";

  revision 2017-11-20 {
    description "First version of the separated relay specific
      YANG model.";

    reference "I-D: draft-ietf-dhc-dhcpv6-yang";
  }

  /*
   * Grouping
   */

  grouping vendor-infor {
   description "Vendor information.";
   container vendor-info {
     description "";
     leaf ent-num {
       type uint32;
       mandatory true;
       description "enterprise number";
     }
     leaf-list data {
       type string;
       description "specific vendor info";
     }
   }
  }

  /*
   * Data Nodes
   */

container relay {
    presence "Enables relay";
    description "dhcpv6 relay portion";
    container relay-attributes {
      description "A container describes
        some basic attributes of the relay
        agent including some relay agent
        specific options data that need to
        be configured previously. Such options
        include Remote-Id option and
        Subscriber-Id option.";
      leaf name {
        type string;
        description "relay agent name";
      }
      leaf description {
        type string;
        description "description of the relay agent";
      }
      leaf-list dest-addrs {
        type inet:ipv6-address;
        description "Each DHCPv6 relay agent may
          be configured with a list of destination
          addresses. This node defines such a list
          of IPv6 addresses that may include
          unicast addresses, multicast addresses
          or other addresses.";
      }
      list subscribers {
        key subscriber;
        description "subscribers";
        leaf subscriber {
          type uint8;
          mandatory true;
          description "subscriber";
        }
        leaf subscriber-id {
          type string;
          mandatory true;
          description "subscriber id";
        }
      }
      list remote-host {
        key ent-num;
        description "remote host";
        leaf ent-num {
          type uint32;
          mandatory true;
          description "enterprise number";
        }
        leaf remote-id {
          type string;
          mandatory true;
          description "remote id";
        }
      }
      uses vendor-infor;
    }

    container rsoo-option-sets {
      list option-set {
        key id;
          leaf id {
            type uint32;
          }
        uses dhcpv6-options:relay-supplied-option-definitions;
      }
    }

    list relay-if {
      // if - This should reference an entry in ietf-interfaces
      key if-name;
      description "A relay agent may have several
        interfaces, we should provide a way to configure
        and manage parameters on the interface-level. A
        list that describes specific interfaces and
        their corresponding parameters is employed to
        fulfil the configfuration. Here we use a string
        called 'if-name; as the key of list.";
      leaf if-name {
        type string;
        mandatory true;
        description "interface name";
      }
      leaf enable {
        type boolean;
        mandatory true;
        description
          "whether this interface is enabled";
      }
      leaf ipv6-address {
        type inet:ipv6-address;
        description
          "ipv6 address for this interface";
      }
      leaf interface-id {
        type string;
        description "interface id";
      }
      leaf rsoo-option-set-id {
        type leafref {
          path "/relay/rsoo-option-sets/option-set/id";
        }
        description "Configured Relay Supplied Option set";
      }
      list pd-route {
        // if - need to look at if/how we model these. If they are
        // going to be modelled, then they should be ro state
        // entries (we're not trying to configure routes here)
        key pd-route-id;
        description "pd route";
        leaf pd-route-id {
          type uint8;
          mandatory true;
          description "pd route id";
        }
        leaf requesting-router-id {
          type uint32;
          mandatory true;
          description "requesting router id";
        }
        leaf delegating-router-id {
          type uint32;
          mandatory true;
          description "delegating router id";
        }
        leaf next-router {
          type inet:ipv6-address;
          mandatory true;
          description "next router";
        }
        leaf last-router {
          type inet:ipv6-address;
          mandatory true;
          description "previous router";
        }
      }
      list next-entity {
        key dest-addr;
        description "This node defines
          a list that is used to describe
          the next hop entity of this
          relay distinguished by their
          addresses.";
        leaf dest-addr {
          type inet:ipv6-address;
          mandatory true;
          description "destination addr";
        }
        leaf available {
          type boolean;
          mandatory true;
          description "whether the next entity
            is available or not";
        }
        leaf multicast {
          type boolean;
          mandatory true;
          description "whether the address is
            multicast or not";
        }
        leaf server {
          type boolean;
          mandatory true;
          description "whether the next entity
            is a server";
        }
        container packet-stats {
          config "false";
          description "packet statistics";
          leaf cli-packet-rvd-count {
            type uint32;
            mandatory true;
            description "client received packet
              counter";
          }
          leaf solicit-rvd-count {
            type uint32;
            mandatory true;
            description
              "solicit received counter";
          }
          leaf request-rvd-count {
            type uint32;
            mandatory true;
            description
              "request received counter";
          }
          leaf renew-rvd-count {
            type uint32;
            mandatory true;
            description
              "renew received counter";
          }
          leaf rebind-rvd-count {
            type uint32;
            mandatory true;
            description
              "rebind recevied counter";
          }
          leaf decline-rvd-count {
            type uint32;
            mandatory true;
            description
              "decline received counter";
          }
          leaf release-rvd-count {
            type uint32;
            mandatory true;
            description
              "release received counter";
          }
          leaf info-req-rvd-count {
            type uint32;
            mandatory true;
            description
              "information request counter";
          }
          leaf relay-for-rvd-count {
            type uint32;
            mandatory true;
            description
              "relay forward received counter";
          }
          leaf relay-rep-rvd-count {
            type uint32;
            mandatory true;
            description
              "relay reply received counter";
          }
          leaf packet-to-cli-count {
            type uint32;
            mandatory true;
            description
              "packet to client counter";
          }
          leaf adver-sent-count {
            type uint32;
            mandatory true;
            description
              "advertisement sent counter";
          }
          leaf confirm-sent-count {
            type uint32;
            mandatory true;
            description
              "confirm sent counter";
          }
          leaf reply-sent-count {
            type uint32;
            mandatory true;
            description
              "reply sent counter";
          }
          leaf reconfig-sent-count {
            type uint32;
            mandatory true;
            description
              "reconfigure sent counter";
          }
          leaf relay-for-sent-count {
            type uint32;
            mandatory true;
            description
              "relay forward sent counter";
          }
          leaf relay-rep-sent-count {
            type uint32;
            mandatory true;
            description
              "relay reply sent counter";
          }
        }
      }
    }
    container relay-stats {
      config "false";
      description "relay statistics";
      leaf cli-packet-rvd-count {
        type uint32;
        mandatory true;
        description "client packet received counter";
      }
      leaf relay-for-rvd-count {
        type uint32;
        mandatory true;
        description "relay forward received counter";
      }
      leaf relay-rep-rvd-count {
        type uint32;
        mandatory true;
        description "relay reply recevied counter";
      }
      leaf packet-to-cli-count {
        type uint32;
        mandatory true;
        description "packet to client counter";
      }
      leaf relay-for-sent-count {
        type uint32;
        mandatory true;
        description "relay forward sent counter";
      }
      leaf relay-rep-sent-count {
        type uint32;
        mandatory true;
        description "relay reply sent counter";
      }
      leaf discarded-packet-count {
        type uint32;
        mandatory true;
        description "discarded packet counter";
      }
    }
  }

  /*
   * Notifications
   */

  notification notifications {
    container dhcpv6-relay-event {
      description "dhcpv6 relay event";
      container topo-changed {
        description "raised when the topology
          of the relay agent is changed.";
        leaf relay-if-name {
          type string;
          mandatory true;
          description "relay interface name";
        }
        leaf first-hop {
          type boolean;
          mandatory true;
          description "first hop";
        }
        leaf last-entity-addr {
          type inet:ipv6-address;
          mandatory true;
          description "last entity address";
        }
      }
    }
  }
}
