module ietf-dhcpv6-client {
  yang-version 1.1;
  namespace "urn:ietf:params:xml:ns:yang:ietf-dhcpv6-client";
  prefix "dhcpv6-client";

  import ietf-inet-types {
    prefix inet;
    revision-date "2013-07-15";
  }
  import ietf-yang-types {
    prefix yang;
    revision-date "2013-07-15";
  }
  import ietf-dhcpv6-options {
    prefix dhcpv6-options;
    revision-date "2017-11-24";
  }

  organization "DHC WG";
  contact "yong@csnet1.cs.tsinghua.edu.cn
    wangh13@mails.tsinghua.edu.cn
    lh.sunlinh@gmail.com
    ian.farrer@telekom.de
    sladjana.zechlin@telekom.de";

  description "This model defines a YANG data model that can be
    used to configure and manage a DHCPv6 client.";

	
  revision 2017-11-29{
	  description "First version of the seperation of Configuration
		  and State trees.";
	  reference "I-D: draft-ietf-dhc-dhcpv6-yang";
  }
  
  revision 2017-11-24 {
	    description "First version of the separated client specific
	      YANG model.";
  }
  
  /*
   * Grouping
   */

  grouping vendor-infor {
   description "Vendor information.";
   container vendor-info {
     description "";
     leaf ent-num {
       type uint32;
       mandatory true;
       description "enterprise number";
     }
     leaf-list data {
       type string;
       description "specific vendor info";
     }
   }
  }

  grouping duid {
    description "DHCP Unique Identifier";
    reference "RFC3315: Section 9";
    choice duid-type {
      description "Selects the format for the DUID.";
      case duid-llt {
        description "DUID Based on Link-layer Address Plus Time";
        reference "RFC3315 Section 9.2";
        leaf duid-llt-hardware-type {
          type uint16;
          description "Hardware type as assigned by IANA (RFC826).";
        }
        leaf duid-llt-time {
          type yang:timeticks;
          description "The time value is the time that the DUID is generated
            represented in seconds since midnight (UTC), January 1, 2000,
                        modulo 2^32.";
        }
        leaf duid-llt-link-layer-addr {
          type yang:mac-address;
          description "Link-layer address as described in RFC2464";
        }
      }
      case duid-en {
        description "DUID Assigned by Vendor Based on Enterprise Number";
        reference "RFC3315 Section 9.3";
        leaf duid-en-enterprise-number {
          type uint32;
          description "Vendor's registered Private Enterprise Number as
            maintained by IANA";
        }
        leaf duid-en-identifier {
          type string;
          description "Indentifier, unique to the device that is using it";
        }
      }
      case duid-ll {
        description "DUID Based on Link-layer Address";
        reference "RFC3315 Section 9.4";
        leaf duid-ll-hardware-type {
          type uint16;
          description "Hardware type as assigned by IANA (RFC826).";
        }
        leaf duid-ll-time {
          type yang:timeticks;
          description "The time value is the time that the DUID is generated
            represented in seconds since midnight (UTC), January 1, 2000,
            modulo 2^32.";
        }
      }
    }
  }
  grouping portset-para {
    description "portset parameters";
    container port-parameter {
      description "port parameter";
      leaf offset {
        type uint8;
        mandatory true;
        description "offset in a port set";
      }
      leaf psid-len {
        type uint8;
        mandatory true;
        description "length of a psid";
      }
      leaf psid {
        type uint16;
        mandatory true;
        description "psid value";
      }
    }
  }

  grouping iaid {
    container identity-associations {
      config "false";
      description "IA is a construct through which a server and a
        client can identify, group, and manage a set of related IPv6
        addresses. The key of the list is a 4-byte number IAID defined
        in [RFC3315].";
      list identity-association {
        key iaid;
        description "IA";
        leaf iaid {
          type uint32;
          mandatory true;
          description "IAID";
        }
        leaf ia-type {
          type string;
          mandatory true;
          description "IA type";
        }
        leaf-list ipv6-addr {
          type inet:ipv6-address;
          description "ipv6 address";
        }
        leaf-list ipv6-prefix {
          type inet:ipv6-prefix;
          description "ipv6 prefix";
        }
        leaf-list prefix-length {
          type uint8;
          description "ipv6 prefix length";
        }
        leaf t1-time {
          type yang:timeticks;
          mandatory true;
          description "t1 time";
        }
        leaf t2-time {
          type yang:timeticks;
          mandatory true;
          description "t2 time";
        }
        leaf preferred-lifetime {
          type yang:timeticks;
          mandatory true;
          description "preferred lifetime";
        }
        leaf valid-lifetime {
          type yang:timeticks;
          mandatory true;
          description "valid lifetime";
        }
      }
    }
  }

  /*
   * Data Nodes
   */

 container client {
    description "dhcpv6 client portion";
    
    container client-config{
    	description "configuration tree of client";
    	
        container duid {
            description "Sets the DUID";
            uses duid;
          }
          list client-if {
            key if-name;
            description "A client may have several
              interfaces, it is more reasonable to
              configure and manage parameters on
              the interface-level. The list defines
              specific client interfaces and their
              data. Different interfaces are distinguished
              by the key which is a configurable string
              value.";
            leaf if-name {
              type string;
              mandatory true;
              description "interface name";
            }
            leaf cli-id {
              type uint32;
              mandatory true;
              description "client id";
            }
            leaf description {
              type string;
              description
                "description of the client interface";
            }
            leaf pd-function {
              type boolean;
              mandatory true;
              description "Whether the client
                can act as a requesting router
                to request prefixes using prefix
                delegation ([RFC3633]).";
            }
            leaf rapid-commit {
              type boolean;
              mandatory true;
              description "'1' indicates a client can initiate a Solicit-Reply
                message exchange by adding a Rapid Commit option in Solicit
                message. '0' means the client is not allowed to add a Rapid
                Commit option to request addresses in a two-message exchange
                pattern.";
            }
            container mo-tab {
              description "The management tab label indicates the operation
                mode of the DHCPv6 client. 'm'=1 and 'o'=1 indicate the
                client will use DHCPv6 to obtain all the configuration data.
                'm'=1 and 'o'=0 are a meaningless combination. 'm'=0 and 'o'=1
                indicate the client will use stateless DHCPv6 to obtain
                configuration data apart from addresses/prefixes data.
                'm'=0 and 'o'=0 represent the client will not use DHCPv6
                but use SLAAC to achieve configuration.";
                // if - not sure about the intended use here as it seems
                // to be redfining what will be received in the PIO. Is
                // the intention to be whether they PIO options will be
                // obeyed as received or overridden?
              leaf m-tab {
                type boolean;
                mandatory true;
                description "m tab";
              }
              leaf o-tab {
                type boolean;
                mandatory true;
                description "o tab";
              }
            }
            container client-configured-options {
              description "client configured options";
              uses dhcpv6-options:client-option-definitions;
            }
    }
    
    
    }
    
    container client-state{
    	description "state tree of client";
    	
    	config "false";
        container if-other-paras {
            description "A client can obtain
              extra configuration data other than
              address and prefix information through
              DHCPv6. This container describes such
              data the client was configured. The
              potential configuration data may
              include DNS server addresses, SIP
              server domain names, etc.";
            uses dhcpv6-options:server-option-definitions;

            container supported-options {
              // if - Unclear on what this container is used for. Maybe
              // putting options as 'features' could replace this.
              description "supported options";
              list supported-option {
                key option-code;
                description "supported option";
                leaf option-code {
                  type uint16;
                  mandatory true;
                  description "option code";
                }
                leaf description {
                  type string;
                  mandatory true;
                  description
                    "description of supported option";
                }
              }
            }
          }
    }
  }

  /*
   * Notifications
   */

  notification notifications {
    container dhcpv6-client-event {
      description "dhcpv6 client event";
      container ia-lease-event {
        description "raised when the
          client was allocated a new IA from
          the server or it renew/rebind/release
          its current IA";
        leaf event-type {
          type enumeration{
            enum "allocation" {
              description "allocate";
            }
            enum "rebind" {
              description "rebind";
            }
            enum "renew" {
              description "renew";
            }
            enum "release" {
              description "release";
            }
          }
          mandatory true;
          description "event type";
        }
        container duid {
          description "Sets the DUID";
          uses duid;
        }
        leaf iaid {
          type uint32;
          mandatory true;
          description "IAID";
        }
        leaf serv-name {
          type string;
          description "server name";
        }
        leaf description {
          type string;
          description "description of event";
        }
      }
      container invalid-ia-detected {
        description "raised when the identity
          association of the client can be proved
          to be invalid.  Possible condition includes
          duplicated address, illegal address, etc.";
        container duid {
          description "Sets the DUID";
          uses duid;
        }
        leaf cli-duid {
          type uint32;
          mandatory true;
          description "duid of client";
        }
        leaf iaid {
          type uint32;
          mandatory true;
          description "IAID";
        }
        leaf serv-name {
          type string;
          description "server name";
        }
        leaf description {
          type string;
          description "description of the event";
        }
      }
      container retransmission-failed {
        description "raised when the retransmission
          mechanism defined in [RFC3315] is failed.";
        container duid {
          description "Sets the DUID";
          uses duid;
        }
        leaf description {
          type enumeration {
            enum "MRC failed" {
              description "MRC failed";
            }
            enum "MRD failed" {
              description "MRD failed";
            }
          }
          mandatory true;
          description "description of failure";
        }
      }
      container failed-status-turn-up {
        description "raised when the client receives
          a message includes an unsuccessful Status Code
          option.";
        container duid {
          description "Sets the DUID";
          uses duid;
        }
        leaf status-code {
          type enumeration {
            enum "1" {
              description "UnspecFail";
            }
            enum "2" {
              description "NoAddrAvail";
            }
            enum "3" {
              description "NoBinding";
            }
            enum "4" {
              description "NotOnLink";
            }
            enum "5" {
              description "UseMulticast";
            }
          }
          mandatory true;
          description "employed status code";
        }
      }
    }
  }
}
