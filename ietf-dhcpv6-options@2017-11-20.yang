module ietf-dhcpv6-options {
  namespace "urn:ietf:params:xml:ns:yang:ietf-dhcpv6-options";
  prefix "dhcpv6-options";

  import ietf-inet-types {
    prefix inet;
    revision-date "2013-07-15";
  }
  import ietf-yang-types {
    prefix yang;
    revision-date "2013-07-15";
  }

  organization "DHC WG";
  contact "yong@csnet1.cs.tsinghua.edu.cn
    wangh13@mails.tsinghua.edu.cn
    lh.sunlinh@gmail.com
    ian.farrer@telekom.de
    sladjana.zechlin@telekom.de";

  description "This model defines a YANG data model that can be
    used to configure and manage a DHCPv6 server.";

  revision 2017-11-20 {
    description "First version of the separated DHCPv6 options
      YANG model.";

    reference "I-D:draft-ietf-dhc-dhcpv6-yang";
  }

  /*
   * Features
   */

  /*
   * Groupings
   */

  grouping portset-para {
   description "portset parameters";
   container port-parameter {
     description "port parameter";
     leaf offset {
       type uint8;
       mandatory true;
       description "offset in a port set";
     }
     leaf psid-len {
       type uint8;
       mandatory true;
       description "length of a psid";
     }
     leaf psid {
       type uint16;
       mandatory true;
       description "psid value";
     }
   }
  }

  grouping server-option-definitions {
    description "Contains definitions for options configured on the
      DHCPv6 server which will be supplied to clients.";
    container server-unicast-option {
      description "OPTION_UNICAST (12) Server Unicast Option";
      reference "RFC3315: Dynamic Host Configuration Protocol
      for IPv6 (DHCPv6)";
      leaf server-address {
        type inet:ipv6-address;
      }
    }
    container sip-server-option {
      description "OPTION_SIP_SERVER_D (21) SIP Servers Domain Name List
      and OPTION_SIP_SERVER_A (22) SIP Servers IPv6 Address List";
      /* if - Note - this container is currently modelling two options
       (21 & 22). It would allow the config of a mixed list of domain
       names and addresses in a way that doesn't follow the
       RFC. Needs to be broken into SIP Domain list and SIP Address
       list containers */
      reference "RFC3319: Dynamic Host Configuration Protocol
        (DHCPv6) Options for Session Initiation Protocol (SIP)
        Servers";
      leaf enable {
        type boolean;
        mandatory true;
        description "Indicate whether this option will be included in
          the option set";
      }
      list sip-server {
        key sip-serv-id;
        description "sip server info";
        leaf sip-serv-id {
          type uint8;
          mandatory true;
          description "sip server id";
        }
        leaf sip-serv-domain-name {
          type string;
          mandatory true;
          description "sip server domain
            name";
        }
        leaf sip-serv-addr {
          type inet:ipv6-address;
          mandatory true;
          description "sip server addr";
        }
      }
    }
    container dns-config-option {
      description "OPTION_DNS_SERVERS (23) DNS recursive Name
        Server option";
      reference "RFC3646: DNS Configuration options for Dynamic
        Host Configuration Protocol for IPv6 (DHCPv6)";
      leaf enable {
        type boolean;
        mandatory true;
        description "indicate whether this
          option will be included in the
          option set";
      }
      list dns-server {
        key dns-serv-id;
        description "dns server info";
        leaf dns-serv-id {
          type uint8;
          mandatory true;
          description "DNS server list entry ID.";
        }
        leaf dns-serv-addr {
          type inet:ipv6-address;
          mandatory true;
          description "DNS server address.";
        }
      }
    }
    container domain-searchlist-option {
      description "OPTION_DOMAIN_LIST (24) Domain Search List Option";
      reference "RFC3646: DNS Configuration options for Dynamic
        Host Configuration Protocol for IPv6 (DHCPv6)";
      leaf enable {
        type boolean;
        mandatory true;
        description "indicate whether this
          option will be included in the
          option set";
      }
      list domain-searchlist {
        key domain-searchlist-id;
        description "dns server info";
        leaf domain-searchlist-id {
          type uint8;
          mandatory true;
          description "Domain seachlist entry ID.";
        }
        leaf domain-search-list-entry {
          type string;
          mandatory true;
          description "Domain search list entry.";
        }
      }
    }
    container nis-config-option {
      description "OPTION_NIS_SERVERS (27) Network Information Service (NIS)
        Servers Option.";
      reference "RFC3989: Network Information Service (NIS) Configuration
        Options for Dynamic Host Configuration Protocol for IPv6 (DHCPv6)";
      leaf enable {
        type boolean;
        mandatory true;
        description "indicate whether this
          option will be included in the
          option set";
      }
      list nis-server {
        key nis-serv-id;
        description "nis server info";
        leaf nis-serv-id {
          type uint8;
          mandatory true;
          description "nis server id";
        }
        leaf nis-serv-addr {
          type inet:ipv6-address;
          mandatory true;
          description "nis server addr";
        }
      }
    }
    container nis-plus-config-option {
      description "OPTION_NISP_SERVERS (28): Network Information Service V2
        (NIS+) Servers Option.";
      reference "RFC3989: Network Information Service (NIS) Configuration
        Options for Dynamic Host Configuration Protocol for IPv6 (DHCPv6)";
      leaf enable {
        type boolean;
        mandatory true;
        description "indicate whether this
          option will be included in the
          option set";
      }
      list nis-plus-server {
        key nis-plus-serv-id;
        description "NIS+ server information.";
        leaf nis-plus-serv-id {
          type uint8;
          mandatory true;
          description "nisp server id";
        }
        leaf nis-plus-serv-addr {
          type inet:ipv6-address;
          mandatory true;
          description "nisp server addr";
        }
      }
    }
    container nis-domain-name {
      description "OPTION_NIS_DOMAIN_NAME (29) Network Information
        Service (NIS) Domain Name Option";
      reference "RFC3989: Network Information Service (NIS)
        Configuration Options for Dynamic Host Configuration Protocol
        for IPv6 (DHCPv6)";
      leaf enable {
        type boolean;
        mandatory true;
        description "indicate whether this
          option will be included in the
          option set";
      }
      leaf nis-domain-name {
        type string;
        description "The Network Information Service (NIS) Domain Name
        option is used by the server to convey client's NIS Domain Name
        info to the client.";
      }
    }
    container sntp-server-option {
      description "OPTION_SNTP_SERVERS (31) Simple Network Time Protocol
        (SNTP) Servers Option";
      reference "RFC4075: Simple Network Time Protocol (SNTP) Configuration
        Option for DHCPv6";
      leaf enable {
        type boolean;
        mandatory true;
        description "indicate whether this
          option will be included in the
          option set";
      }
      list sntp-server {
        key sntp-serv-id;
        description "sntp server info";
        leaf sntp-serv-id {
          type uint8;
          mandatory true;
          description "sntp server id";
        }
        leaf sntp-serv-addr {
          type inet:ipv6-address;
          mandatory true;
          description "sntp server addr";
        }
      }
    }
    container info-refresh-time-option {
      description "OPTION_INFORMATION_REFRESH_TIME (32) Information Refresh
        Time option.";
      reference "RFC4242: Information Refresh Time Option for Dynamic Host
        Configuration Protocol for IPv6 (DHCPv6";
      leaf enable {
        type boolean;
        mandatory true;
        description "indicate whether this
         option will be included in the
         option set";
      }
      leaf info-refresh-time {
        type yang:timeticks;
        mandatory true;
        description "The refresh time.";
      }
    }
    container cli-fqdn-option {
      description "OPTION_CLIENT_FQDN (39) DHCPv6 Client FQDN Option";
      reference "RFC4704: The Dynamic Host Configuration Protocol for IPv6
        (DHCPv6) Client Fully Qualified Domain Name (FQDN) Option";
      leaf enable {
        type boolean;
        mandatory true;
        description "indicate whether this option will be included in the
          option set";
      }
      leaf server-initiate-update {
        type boolean;
        mandatory true;
        description "server initiate";
      }
      leaf client-initiate-update {
        type boolean;
        mandatory true;
        description "client initiate";
      }
      leaf modify-name-from-cli {
        type boolean;
        mandatory true;
        description "modify by client";
      }
    }
    container posix-timezone-option {
      description "OPTION_NEW_POSIX_TIMEZONE (41) Posix Timezone option";
      reference "RFC4822: Timezone Options for DHCP";
      leaf enable {
        type boolean;
        mandatory true;
        description "indicate whether this option will be included in the
          option set";
      }
      leaf tz-posix {
        type string;
        mandatory true;
        description "TZ Posix IEEE 1003.1 String";
      }
    }
    container posix-timezone-option-db-option {
      description "OPTION_NEW_TZDB_TIMEZONE (42) Timezone Database option";
      reference "RFC4822: Timezone Options for DHCP";
      leaf enable {
        type boolean;
        mandatory true;
        description "indicate whether this option will be included in the
          option set";
      }
      leaf tz-database {
        type string;
        mandatory true;
        description "Reference to the TZ Database";
      }
    }
    container ntp-server-option {
      //This option looks like it needs work to correctly model the
      //option as defined in the RFC.
      description "OPTION_NTP_SERVER (56) NTP Server Option for DHCPv6";
      reference "RFC5908: Network Time Protocol (NTP) Server Option for
      DHCPv6";
      leaf enable {
        type boolean;
        mandatory true;
        description "indicate whether this option will be included in the
          option set";
      }
      list ntp-server {
        key ntp-serv-id;
        description "ntp server info";
        leaf ntp-serv-id {
          type uint8;
          mandatory true;
          description "ntp server id";
        }
        leaf ntp-serv-addr-suboption {
          type inet:ipv6-address;
          mandatory true;
          description "ntp server addr";
        }
        leaf ntp-serv-mul-addr-suboption {
          type inet:ipv6-address;
          mandatory true;
          description "ntp server multicast addr";
        }
        leaf ntp-serv-fqdn-suboption {
          type string;
          mandatory true;
          description "ntp server fqdn";
        }
      }
    }
    container network-boot-option {
      description "OPT_BOOTFILE_URL (59) and OPT_BOOTFILE_PARAM (60)";
      reference "RFC5970: DHCPv6 Options for Network Boot";
      // if - Looks like 2 options combined that need to be split out
      leaf enable {
        type boolean;
        mandatory true;
        description "indicate whether this
          option will be included in the
          option set";
      }
      list boot-file {
        key boot-file-id;
        description "boot file info";
        leaf boot-file-id {
          type uint8;
          mandatory true;
          description "boot file id";
        }
        leaf-list suitable-arch-type {
          type uint16;
          description "architecture type";
        }
        leaf-list suitable-net-if {
          type uint32;
          description "network interface";
        }
        leaf boot-file-url {
          type string;
          mandatory true;
          description "url for boot file";
        }
        list boot-file-paras {
          key para-id;
          description "boot file parameters";
          leaf para-id {
            type uint8;
            mandatory true;
            description "parameter id";
          }
          leaf parameter {
            type string;
            mandatory true;
            description "parameter
              value";
          }
        }
      }
    }
    container aftr-name-option {
      description "OPTION_AFTR_NAME (64) AFTR-Name DHCPv6 Option";
      reference "RFC6334: Dynamic Host Configuration Protocol for IPv6
      (DHCPv6) Option for Dual-Stack Lite";
      leaf enable {
        type boolean;
        mandatory true;
        description "indicate whether this option will be included in the
        option set";
      }
      leaf tunnel-endpoint-name {
        type string;
        mandatory true;
        description "aftr name";
      }
    }
    container kerberos-option {
      //This needs re-working and possibly splitting into several option
      //containers to follow the RFC.
      description "OPTION_KRB_KDC (78) Kerberos KDB Option, OPTION_KRB_REALM_NAME (76)
        Kerberos Realm Name Option and OPTION_KRB_DEFAULT_REALM_NAME (77)
        Kerberos Default Realm Name Option";
      reference "RFC6784: Kerberos Options for DHCPv6";
      leaf enable {
        type boolean;
        mandatory true;
        description "indicate whether this
          option will be included in the
          option set";
      }
      leaf default-realm-name {
        type string;
        mandatory true;
        description "default realm name";
      }
      list kdc-info {
        key kdc-id;
        description "kdc info";
        leaf kdc-id {
          type uint8;
          mandatory true;
          description "kdc id";
        }
        leaf priority {
          type uint16;
          mandatory true;
          description "priority";
        }
        leaf weight {
          type uint16;
          mandatory true;
          description "weight";
        }
        leaf transport-type {
          type uint8;
          mandatory true;
          description "transport type";
        }
        leaf port-number {
          type uint16;
          mandatory true;
          description "port number";
        }
        leaf kdc-ipv6-addr {
          type inet:ipv6-address;
          mandatory true;
          description "kdc ipv6 addr";
        }
        leaf realm-name {
          type string;
          mandatory true;
          description "realm name";
        }
      }
    }
    container sol-max-rt-option {
      description "OPTION_SOL_MAX_RT (82) sol max rt option";
      reference "RFC7083: Modification to Default Values of
        SOL_MAX_RT and INF_MAX_RT";
      leaf enable {
        type boolean;
        mandatory true;
        description "indicate whether this
          option will be included in the
          option set";
        }
        leaf sol-max-rt-value {
          type yang:timeticks;
          mandatory true;
          description "sol max rt value";
        }
    }
    container inf-max-rt-option {
      description "OPTION_INF_MAX_RT (83) inf max rt option";
      reference "RFC7083: Modification to Default Values of
        SOL_MAX_RT and INF_MAX_RT";
      leaf enable {
        type boolean;
        mandatory true;
        description "indicate whether this
          option will be included in the
          option set";
      }
      leaf inf-max-rt-value {
        type yang:timeticks;
        mandatory true;
        description "inf max rt value";
      }
    }
    container addr-selection-option {
      description "OPTION_ADDRSEL (84) and OPTION_ADDRSEL_TABLE (85)";
      reference "RFC7078: Distributing Address Selection Policy Using
      DHCPv6";
      // if - Needs checking to see if this matches the RFC - there
      // are two options here.
      leaf enable {
        type boolean;
        mandatory true;
        description "indicate whether this option will be included in the
                  option set";
        }
      leaf a-bit-set {
        type boolean;
        mandatory true;
        description "a bit";
      }
      leaf p-bit-set {
        type boolean;
        mandatory true;
        description "p bit";
      }
      list policy-table {
        key policy-id;
        description "policy table";
        leaf policy-id {
          type uint8;
          mandatory true;
          description "policy id";
        }
        leaf label {
          type uint8;
          mandatory true;
          description "label";
        }
        leaf precedence {
          type uint8;
          mandatory true;
          description "precedence";
        }
        leaf prefix-len {
          type uint8;
          mandatory true;
          description "prefix length";
        }
        leaf prefix {
          type inet:ipv6-prefix;
          mandatory true;
          description "prefix";
        }
      }
    }
    container pcp-server-option {
      description "OPTION_V6_PCP_SERVER (86)
        pcp server option";
      reference "RFC7291: DHCP Options for the Port Control
        Protocol (PCP)";
      leaf enable {
        type boolean;
        mandatory true;
        description "indicate whether this option will be included
          in the option set";
      }
      list pcp-server {
        key pcp-serv-id;
        description "pcp server info";
        leaf pcp-serv-id {
          type uint8;
          mandatory true;
          description "pcp server id";
        }
        leaf pcp-serv-addr {
          type inet:ipv6-address;
          mandatory true;
          description "pcp server addr";
        }
      }
    }
    container s46-rule-option {
      description "OPTION_S46_RULE (89) S46 rule option";
      reference "RFC7598: DHCPv6 Options for Configuration of
        Softwire Address and Port-Mapped Clients";
      leaf enable {
        type boolean;
        mandatory true;
        description "indicate whether this option will be included
          in the option set";
      }
      list s46-rule {
        key rule-id;
        description "s46 rule";
        leaf rule-id {
          type uint8;
          mandatory true;
          description "rule id";
        }
        leaf rule-type {
          type enumeration {
            enum "BMR" {
            description "BMR";
          }
          enum "FMR" {
            description "FMR";
          }
        }
        mandatory true;
        description "rule type";
      }
      leaf prefix4-len {
        type uint8;
        mandatory true;
        description "ipv4 prefix length";
      }
        leaf ipv4-prefix {
          type inet:ipv4-prefix;
          mandatory true;
          description "ipv4 prefix";
        }
        leaf prefix6-len {
          type uint8;
          mandatory true;
          description "ipv6 prefix length";
        }
        leaf ipv6-prefix {
          type inet:ipv6-prefix;
          mandatory true;
          description "ipv6 prefix";
        }
        uses portset-para;
      }
    }
    container s46-br-option {
      description "OPTION_S46_BR (90) S46 BR Option";
      reference "RFC7598: DHCPv6 Options for Configuration of
        Softwire Address and Port-Mapped Clients";
      leaf enable {
        type boolean;
        mandatory true;
        description "indicate whether this option will be included
          in the option set";
      }
      list br {
        key br-id;
        description "br info";
        leaf br-id {
          type uint8;
          mandatory true;
          description "br id";
        }
        leaf br-ipv6-addr {
          type inet:ipv6-address;
          mandatory true;
          description "br ipv6 addr";
        }
      }
    }
    container s46-dmr-option {
      description "OPTION_S46_DMR (91) S46 DMR Option";
      reference "RFC7598: DHCPv6 Options for Configuration of
        Softwire Address and Port-Mapped Clients";
      leaf enable {
        type boolean;
        mandatory true;
        description "indicate whether this
          option will be included in the
          option set";
      }
      list dmr {
        key dmr-id;
        description "dmr info";
        leaf dmr-id {
          type uint8;
          mandatory true;
          description "dmr id";
        }
        leaf dmr-prefix-len {
          type uint8;
          mandatory true;
          description "dmr prefix length";
        }
        leaf dmr-ipv6-prefix {
          type inet:ipv6-prefix;
          mandatory true;
          description "dmr ipv6 prefix";
        }
      }
    }
    container s46-v4-v6-binding-option {
      description "OPTION_S46_V4V6BIND (92) S46 IPv4/IPv6 Address
        Binding option";
      reference "RFC7598: DHCPv6 Options for Configuration of
        Softwire Address and Port-Mapped Clients";
      leaf enable {
        type boolean;
        mandatory true;
        description "indicate whether this
          option will be included in the
          option set";
      }
      list ce {
        key ce-id;
        description "ce info";
        leaf ce-id {
          type uint8;
          mandatory true;
          description "ce id";
        }
        leaf ipv4-addr {
          type inet:ipv4-address;
          mandatory true;
          description "ce ipv4 addr";
        }
        leaf bind-prefix6-len {
          type uint8;
          mandatory true;
          description "bind ipv6 prefix
            length";
        }
        leaf bind-ipv6-prefix {
          type inet:ipv6-prefix;
          mandatory true;
          description "bind ipv6 prefix";
        }
        uses portset-para;
      }
    }
  }
  //if - NB - The list of options needs to be updated.

  grouping relay-supplied-option-definitions {
    // if - The structure here needs to be checked and probably reworked.
    description "Relay supplied DHCP Options";
    reference "RFC6422: Relay-Supplied DHCP Options";
    container erp-local-domain-name-option {
      description "OPTION_ERP_LOCAL_DOMAIN_NAME (65) DHCPv6 ERP Local
        Domain Name Option";
      reference "RFC6440: The EAP Re-authentication Protocol (ERP)
        Local Domain Name DHCPv6 Option";
      leaf enable {
        type boolean;
        mandatory true;
        description "indicate whether
          this option is included in the
          rsoo set";
      }
      list erp-for-client {
        key cli-id;
        description "erp for client";
        leaf cli-id {
          type uint32;
          mandatory true;
          description "client id";
        }
        container duid {
          description "Sets the DUID";
          // uses duid;
          // if - Maybe DUID definition needs to be moved to this module.
        }
        leaf erp-name {
          type string;
          mandatory true;
          description "erp name";
        }
      }
    }
  }

  grouping client-option-definitions {
    description "Contains definitions for options configured on the
      DHCPv6 client which will be sent to the server.";
    list new-or-standard-cli-option {
      key option-code;
      description "new or standard client option";
      leaf option-code {
        type uint16;
        mandatory true;
        description "option code";
      }
      leaf option-name {
        type string;
        mandatory true;
        description "option name";
      }
      leaf option-description {
        type string;
        mandatory true;
        description "description of client
          option";
      }
      leaf option-reference {
        type string;
        description "the reference of option";
      }
      leaf option-value {
        type string;
        mandatory true;
        description "the option value";
      }
    }
    container option-request-option {
      description "OPTION_ORO (6) Option Request Option";
      reference "RFC3315: Dynamic Host Configuration Protocol
      for IPv6 (DHCPv6)";
      list oro-option {
        key option-code;
        description "oro option";
        leaf option-code {
          type uint16;
          mandatory true;
          description "option code";
        }
        leaf description {
          type string;
          mandatory true;
          description "description of oro
            options";
        }
      }
    }
    container rapid-commit-option {
      description "OPTION_RAPID_COMMIT (14)";
      reference "RFC3315: Dynamic Host Configuration Protocol
      for IPv6 (DHCPv6)";
      leaf enable-rapid-commit {
        type boolean;
      }
      // if - This fuction is also being covered by
      // /client/client-if/rapid-commit switch. Is it better
      // defined there or as an option?
    }
    container user-class-option {
      description "OPTION_USER_CLASS (15) User Class Option";
      reference "RFC3315: Dynamic Host Configuration Protocol
      for IPv6 (DHCPv6)";
      leaf enable {
        type boolean;
        mandatory true;
        description "indicate whether this
          option will be configured at the
          client";
      }
      list user-class {
        key user-class-id;
        description "user class";
        leaf user-class-id {
          type uint8;
          mandatory true;
          description "user class id";
        }
        leaf user-class-data {
          type string;
          mandatory true;
          description "The information contained in the data area
            of this option is contained in one or more opaque
            fields that represent the user class or classes of
            which the client is a member. ";
        }
      }
    }
    container vendor-class-option {
      description "OPTION_VENDOR_CLASS (16) Vendor Class Option";
      reference "RFC3315: Dynamic Host Configuration Protocol
      for IPv6 (DHCPv6)";
      leaf enable {
        type boolean;
        mandatory true;
        description "indicate whether this
          option will be configured at the
          client";
      }
      leaf enterprise-number {
        type uint32;
        mandatory true;
        description "enterprise number";
      }
      leaf-list vendor-class-data {
        type string;
        description "The vendor-class-data is composed of a series
          of separate items, each of which describes some
          characteristic of the client's hardware configuration.
          Examples of vendor-class-data instances might include the
          version of the operating system the client is running or
          the amount of memory installed on the client.";
          // if - It may be better to model this as a leaf-list
          // so the list contents can be indexed.
      }
    }
    container client-fqdn-option {
      description "OPTION_CLIENT_FQDN (39) The Dynamic Host
        Configuration Protocol for IPv6 (DHCPv6) Client Fully
        Qualified Domain Name (FQDN) Option";
      reference "RFC4704: The Dynamic Host Configuration Protocol
        for IPv6 (DHCPv6) Client Fully Qualified Domain Name (FQDN)
        Option";
      leaf enable {
        type boolean;
        mandatory true;
        description "indicate whether this
          option will be configured at the
          client";
      }
      leaf fqdn {
        type string;
        mandatory true;
        description "fqdn";
      }
      leaf server-initiate-update {
        type boolean;
        mandatory true;
        description "whether server initiate";
      }
      leaf client-initiate-update {
        type boolean;
        mandatory true;
        description "whether client initiate";
      }
    }
    container client-arch-type-option {
      description "OPTION_CLIENT_ARCH_TYPE (61) Client System
        Architecture Type Option";
      reference "RFC5970: DHCPv6 Options for Network Boot";
      leaf enable {
        type boolean;
        mandatory true;
        description "indicate whether this
          option will be configured at the
          client";
      }
      list architecture-types {
        key type-id;
        description "architecture types";
        leaf type-id {
          type uint16;
          mandatory true;
          description "type id";
        }
        leaf most-preferred {
          type boolean;
          mandatory true;
          description "most preferred flag";
        }
      }
    }
    container client-network-interface-identifier-option {
      description
        "OPTION_NII (62) Client Network Interface Identifier
        Option";
      reference "RFC5970: DHCPv6 Options for Network Boot";
      leaf enable {
        type boolean;
        mandatory true;
        description "indicate whether this
          option will be configured at the
          client";
      }
      leaf type {
        type uint8;
        mandatory true;
        description "type";
      }
      leaf major {
        type uint8;
        mandatory true;
        description "major";
      }
      leaf minor {
        type uint8;
        mandatory true;
        description "minor";
      }
    }
    container krb-principal-name-option {
      description "OPTION_KRB_PRINCIPAL_NAME (75) Kerberos
        Principal Name Option";
      reference "RFC6784: Kerberos Options for DHCPv6";
      leaf enable {
        type boolean;
        mandatory true;
        description "indicate whether this
          option will be configured at the
          client";
      }
      leaf principal-name {
        type string;
        mandatory true;
        description "principal name";
        // if - this can probably be typed according to RFC4120 5.2.2
      }
    }
    container client-link-layer-addr-option {
      description "OPTION_CLIENT_LINKLAYER_ADDR (79) DHCPv6 Client
        Link-Layer Address Option";
      reference "RFC6939: Client Link-Layer Address Option in
        DHCPv6";
      leaf enable {
        type boolean;
        mandatory true;
        description "indicate whether this option will be configured
          at the client";
      }
      leaf link-layer-type {
        type uint16;
        mandatory true;
        description "Client link-layer address type. The link-layer
          type MUST be a valid hardware type assigned by the IANA,
          as described in [RFC0826]";
      }
      leaf link-layer-addr {
        type string;
        mandatory true;
        description "Client link-layer address";
      }
    }
  }

  grouping custom-option-definitions {
    container operator-option-ipv6-address {
      description "operator ipv6 address option";
      reference "RFC7227: Guidelines for Creating New DHCPv6 Options";
      leaf enable {
        type boolean;
        mandatory true;
        description "indicate whether this
          option will be included in the
          option set";
      }
      list operator-ipv6-addr {
        key operator-ipv6-addr-id;
        description "operator ipv6 address info";
        leaf operator-ipv6-addr-id {
          type uint8;
          mandatory true;
          description "operator ipv6 address id";
        }
        leaf operator-ipv6-addr {
          type inet:ipv6-address;
          mandatory true;
          description "operator ipv6 address id";
        }
      }
    }
    container operator-option-single-flag {
      description "operator single flag";
      reference "RFC7227: Guidelines for Creating New DHCPv6
        Options";
      leaf enable {
        type boolean;
        mandatory true;
        description "indicate whether this
          option will be included in the
          option set";
      }
      list flag {
        key flag-id;
        description "operator single flag info";
        leaf flag-id {
          type uint8;
          mandatory true;
          description "operator single flag id";
        }
        leaf flag-value{
          type boolean;
          mandatory true;
          description "operator single flag value";
        }
      }
    }
    container operator-option-ipv6-prefix {
      description "operator ipv6 prefix option";
      reference "RFC7227: Guidelines for Creating New DHCPv6
        Options";
      leaf enable {
        type boolean;
        mandatory true;
        description "indicate whether this
          option will be included in the
          option set";
      }
      list operator-ipv6-prefix{
        key operator-ipv6-prefix-id;
        description "operator ipv6 prefix info";
        leaf operator-ipv6-prefix-id {
          type uint8;
          mandatory true;
          description "operator ipv6 prefix id";
        }
        leaf operator-ipv6-prefix6-len{
          type uint8;
          mandatory true;
          description "operator ipv6 prefix length";
        }
        leaf operator-ipv6-prefix {
          type inet:ipv6-prefix;
          mandatory true;
          description "operator ipv6 prefix";
        }
      }
    }
    container operator-option-int32 {
      description "operator integer 32 option";
      reference "RFC7227: Guidelines for Creating New DHCPv6
        Options";
      leaf enable {
        type boolean;
        mandatory true;
        description "indicate whether this
          option will be included in the
          option set";
      }
      list int32val{
        key int32val-id;
        description "operator integer 32 info";
        leaf int32val-id {
          type uint8;
          mandatory true;
          description "operator integer 32 id";
        }
        leaf int32val{
          type uint32;
          mandatory true;
          description "operator integer 32 value";
        }
      }
    }
    container operator-option-int16 {
      description "operator integer 16 option";
      reference "RFC7227: Guidelines for Creating New DHCPv6
        Options";
      leaf enable {
        type boolean;
        mandatory true;
        description "indicate whether this
          option will be included in the
          option set";
      }
      list int16val{
        key int16val-id;
        description "operator integer 16 info";
        leaf int16val-id {
          type uint8;
          mandatory true;
          description "operator integer 16 id";
        }
        leaf int16val{
          type uint16;
          mandatory true;
          description "operator integer 16 value";
        }
      }
    }
    container operator-option-int8 {
      description "operator integer 8 option";
      reference "RFC7227: Guidelines for Creating New DHCPv6
        Options";
      leaf enable {
        type boolean;
        mandatory true;
        description "indicate whether this
          option will be included in the
          option set";
      }
      list int8val{
        key int8val-id;
        description "operator integer 8 info";
        leaf int8val-id {
          type uint8;
          mandatory true;
          description "operator integer 8 id";
        }
        leaf int8val{
          type uint8;
          mandatory true;
          description "operator integer 8 value";
        }
      }
    }
    container operator-option-uri {
      description "operator uri option";
      reference "RFC7227: Guidelines for Creating New DHCPv6
        Options";
      leaf enable {
        type boolean;
        mandatory true;
        description "indicate whether this
          option will be included in the
          option set";
      }
      list uri{
        key uri-id;
        description "operator uri info";
        leaf uri-id {
          type uint8;
          mandatory true;
          description "operator uri id";
        }
        leaf uri{
          type string;
          mandatory true;
          description "operator uri value";
        }
      }
    }
    container operator-option-textstring {
      description "operator itext string option";
      reference "RFC7227: Guidelines for Creating New DHCPv6 Options";
      leaf enable {
        type boolean;
        mandatory true;
        description "indicate whether this
          option will be included in the
          option set";
      }
      list textstring{
        key textstring-id;
        description "operator text string info";
        leaf textstring-id {
          type uint8;
          mandatory true;
          description "operator text string id";
        }
        leaf textstring{
          type string;
          mandatory true;
          description "operator text string value";
        }
      }
    }
    container operator-option-var-data {
      description "operator variable length data option";
      reference "RFC7227: Guidelines for Creating New DHCPv6 Options";
      leaf enable {
        type boolean;
        mandatory true;
        description "indicate whether this
          option will be included in the
          option set";
      }
      list int32val{
        key var-data-id;
        description "operator ivariable length data info";
        leaf var-data-id {
          type uint8;
          mandatory true;
          description "operator variable length id";
        }
        leaf var-data{
          type binary;
          mandatory true;
          description "operator variable length value";
        }
      }
    }
    container operator-option-dns-wire {
      description "operator dns wire format domain name list option";
      reference "RFC7227: Guidelines for Creating New DHCPv6
        Options";
      leaf enable {
        type boolean;
        mandatory true;
        description "indicate whether this
          option will be included in the
          option set";
      }
      list operator-option-dns-wire{
        key operator-option-dns-wire-id;
        description "operator dns wire format info";
        leaf operator-option-dns-wire-id {
          type uint8;
          mandatory true;
          description "operator dns wire format id";
        }
        leaf operator-option-dns-wire{
          type binary;
          mandatory true;
          description "operator dns wire format value";
        }
      }
    }
  }
}
